[DOCUMENT]
TITLE: Hello world doc

[REQUIREMENT]
UID: REQ-1
TITLE: Markers inside Doc Comments
STATEMENT: >>>
StrictDoc shall support Rust Doc comments to identify language constructs with
relation markers.
<<<
RATIONALE: >>>
Doc comments are part of the Rust language specification and allow fine grained
and unambigous localization of marked item.
<<<

[REQUIREMENT]
UID: REQ-2
TITLE: Forward Relations
STATEMENT: >>>
StrictDoc shall allow forware relations by predictable, qualified item names to
Rust source code items.
<<<
RELATIONS:
- TYPE: File
  VALUE: example.rs
  FUNCTION: MyModule::my_fn
- TYPE: File
  VALUE: example.rs
  FUNCTION: MyModule::my_fn::my_nested_fn
- TYPE: File
  VALUE: example.rs
  FUNCTION: MyModule::my_fn::my_nested_fn::MY_NESTED_CONST
- TYPE: File
  VALUE: example.rs
  FUNCTION: MyTupleStruct
- TYPE: File
  VALUE: example.rs
  FUNCTION: MyUnion
- TYPE: File
  VALUE: example.rs
  FUNCTION: MyTrait
- TYPE: File
  VALUE: example.rs
  FUNCTION: MyTrait::my_trait_fn
- TYPE: File
  VALUE: example.rs
  FUNCTION: MY_CONST
