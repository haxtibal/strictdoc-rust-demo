[DOCUMENT]
TITLE: Rust support in StrictDoc

[REQUIREMENT]
UID: RUST-DOC-COMMENT
TITLE: Auto-scoped relation markers in Rust docs
STATEMENT: >>>
If a StrictDoc relation marker is inside a `Rust doc comment`_, the marker scope shall be set to exact the item the Rust
language defines as target of the containing doc comment. The :code:`@relation(scope=...)` parameter shall therefore
be optional and shall be ignored if provided.

.. code-block:: rust
   :number-lines:

   /// @relation(REQ-1)
   impl Foo {

       /// @relation(REQ-2)
       fn foo() {
       }
   }

In the given example, the first marker shall link REQ-1 to the :code:`impl Foo` implementation,
highlighting lines 1 to 7. The second marker shall link REQ-2 to the :code:`fn foo()` function,
highlighting lines 4 to 6.

.. _Rust doc comment: https://doc.rust-lang.org/rust-by-example/meta/doc.html#doc-comments
<<<
COMMENT: >>>
Note that doc comments are syntactic sugar for `doc attribute`_ s, which shall also be supported.
To figure detailed doc comment rules from the rust-lang specification it's sometimes useful
to check for general attribute rules, if explicit doc comment rules are missing.

.. _doc attribute: https://doc.rust-lang.org/rustdoc/write-documentation/the-doc-attribute.html
<<<

[REQUIREMENT]
UID: RUST-INNER-DOC-ATTR
TITLE: Inner doc attributes
STATEMENT: >>>
StrictDoc shall support relation markers in inner_ `doc attribute`_ s.

.. _inner: https://doc.rust-lang.org/reference/attributes.html#r-attributes.inner
.. _doc attribute: https://doc.rust-lang.org/rustdoc/write-documentation/the-doc-attribute.html#the-doc-attribute
<<<
RELATIONS:
- TYPE: Parent
  VALUE: RUST-DOC-COMMENT

[REQUIREMENT]
UID: RUST-INNER-LINE-DOC
TITLE: Inner line docs
STATEMENT: >>>
StrictDoc shall support auto-scoped relation relation markers in `inner line docs`_.

.. _inner line docs: https://doc.rust-lang.org/reference/comments.html#grammar-INNER_LINE_DOC
<<<
RELATIONS:
- TYPE: Parent
  VALUE: RUST-DOC-COMMENT

[REQUIREMENT]
UID: RUST-INNER-BLOCK-DOC
TITLE: Inner block docs
STATEMENT: >>>
StrictDoc shall support auto-scoped relation relation markers in `inner block docs`_.

.. _inner block docs: https://doc.rust-lang.org/reference/comments.html#grammar-INNER_BLOCK_DOC
<<<
RELATIONS:
- TYPE: Parent
  VALUE: RUST-DOC-COMMENT

[REQUIREMENT]
UID: RUST-OUTER-DOC-ATTR
TITLE: Outer doc attributes
STATEMENT: >>>
StrictDoc shall support auto-scoped relation markers in outer_ `doc attribute`_ s.

.. _outer: https://doc.rust-lang.org/reference/attributes.html#r-attributes.outer
.. _doc attribute: https://doc.rust-lang.org/rustdoc/write-documentation/the-doc-attribute.html#the-doc-attribute
<<<
RELATIONS:
- TYPE: Parent
  VALUE: RUST-DOC-COMMENT

[REQUIREMENT]
UID: RUST-OUTER-LINE-DOC
TITLE: Outer line docs
STATEMENT: >>>
StrictDoc shall support auto-scoped relation markers in `outer line docs`_.

.. _outer line docs: https://doc.rust-lang.org/reference/comments.html#grammar-OUTER_LINE_DOC
<<<
RELATIONS:
- TYPE: Parent
  VALUE: RUST-DOC-COMMENT

[REQUIREMENT]
UID: RUST-OUTER-BLOCK-DOC
TITLE: Outer block docs
STATEMENT: >>>
StrictDoc shall support auto-scoped relation markers in `outer block docs`_.

.. _outer block docs: https://doc.rust-lang.org/reference/comments.html#railroad-OUTER_BLOCK_DOC
<<<
RELATIONS:
- TYPE: Parent
  VALUE: RUST-DOC-COMMENT

[REQUIREMENT]
UID: RUST-LINE-RANGE
TITLE: File, line and range markers
STATEMENT: >>>
It shall be possible to point to lines of Rust code by using file, line and range markers.
File, line and range markers shall be parsed from `regular line and block comments`_.

Note: File markers may also result from the inner doc comments of the top-level module.

.. _regular line and block comments: https://doc.rust-lang.org/rust-by-example/hello/comment.html#comments
<<<

[REQUIREMENT]
UID: RUST-SOURCE-NODES
TITLE: Source nodes from doc comments
STATEMENT: >>>
If a Rust doc comments contains custom tags, and the containing Rust source file matches an entry in the
source node configuration, StrictDoc shall create document nodes from the custom tags and automatically
link the created node with the Rust item targeted by the doc comment.
<<<

[REQUIREMENT]
UID: RUST-FWD-REL
TITLE: Forward relations to Rust items
STATEMENT: >>>
It shall be possible to link from a requirement in SDoc to a language item in Rust code by using a :code:`FILE`
relation of type :code:`FUNCTION`. For example

.. code-block:: strictdoc

   [REQUIREMENT]
   UID: REQ-1
   RELATIONS:
   - TYPE: File
     VALUE: file.rs
     FUNCTION: file::foo

This shall work for all kinds of Rust items that have a `canonical path`_, including const, enum, fn, mod, static,
struct, trait, type, union.

.. _canonical path: https://doc.rust-lang.org/reference/paths.html#canonical-paths
<<<
RELATIONS:
- TYPE: File
  VALUE: forward_relations.rs
  FUNCTION: forward_relations::FooModule
- TYPE: File
  VALUE: forward_relations.rs
  FUNCTION: forward_relations::FooModule::foo
- TYPE: File
  VALUE: forward_relations.rs
  FUNCTION: forward_relations::FooModule::foo::bar
- TYPE: File
  VALUE: forward_relations.rs
  FUNCTION: forward_relations::FooModule::foo::bar::BAR_CONST
- TYPE: File
  VALUE: forward_relations.rs
  FUNCTION: forward_relations::FooTuple
- TYPE: File
  VALUE: forward_relations.rs
  FUNCTION: forward_relations::FooUnion
- TYPE: File
  VALUE: forward_relations.rs
  FUNCTION: forward_relations::FooTrait
- TYPE: File
  VALUE: forward_relations.rs
  FUNCTION: <forward_relations::FooTuple as forward_relations::FooModule::FooTrait>::foo
- TYPE: File
  VALUE: forward_relations.rs
  FUNCTION: forward_relations::FOO_CONST
- TYPE: File
  VALUE: forward_relations.rs
  FUNCTION: forward_relations::FooEnum

[REQUIREMENT]
UID: RUST-FWD-REL-CANONICAL-PATH
TITLE: Forward relation by canonical path
STATEMENT: >>>
The identifier for forward relations shall be the `canonical path`_ as the rustc compiler would set it when invoked for
a single file like

.. code-block:: shell

   rustc --crate-type rlib --emit=obj src/lib.rs

Note: :code:`cargo build` usually result in a different canonical path, since it considers the file position relative to
the crate root. Using a single file as root is a simplification, needed because StrictDoc is unaware of the Rust
file and directory-based module hierarchy.

.. _canonical path: https://doc.rust-lang.org/reference/paths.html#canonical-paths
<<<
COMMENT: >>>
The canonical path of an item can be observed with :code:`objdump -t lib.o --demangle=rust`. For example, given this
source file

.. code-block:: rust
   :number-lines:

   pub mod foo {

       pub trait Foo {
           fn foo(&self) {}
       }

       pub struct Bar(i32);

       impl Foo for Bar {
           fn foo(&self) {}
       }
   }

:code:`objdump` will show

.. code-block:: shell

   <lib::foo::Bar as lib::foo::Foo>::foo

Alas, a forward relation would be

.. code-block:: strictdoc

   [REQUIREMENT]
   UID: REQ-1
   RELATIONS:
   - TYPE: File
     VALUE: file.rs
     FUNCTION: <lib::foo::Bar as lib::foo::Foo>::foo
<<<
RELATIONS:
- TYPE: Parent
  VALUE: RUST-FWD-REL

[REQUIREMENT]
UID: RUST-COLLAPSE-COMMENTS
TITLE: Collapse doc comments
STATEMENT: >>>
Multiple scattered doc comments should be collapsed as done by the rustdoc_ tool when using the collapse-docs option
to determine the highlight range(s).

For example, rustdoc would collapse alle these comments into the description of :code:`fn foo()`

.. code-block:: rust
   :number-lines:

   /// Some
   /// line

   /// doc,

   /**
     * and some
     * block dock,
     */

   #[doc = "and some"]

   #[doc = "doc attr."]

   fn foo() {
   }

In the given example, the StrictDoc highlight range for the relation marker shall be from line 1 to line 16.

.. _rustdoc: https://github.com/rust-lang/rust/tree/main/src/tools/rustdoc
<<<

[REQUIREMENT]
UID: RUST-MARKER-DESCRIPTION
TITLE: Rust marker descriptions
STATEMENT: >>>
StrictDoc should use the marker labels as rustdoc_ would set them in the description of a documented node.

.. _rustdoc: https://doc.rust-lang.org/stable/rustdoc/
<<<

[REQUIREMENT]
UID: RUST-INNER-DOC-POS
TITLE: Allowed position for inner doc Comment
STATEMENT: >>>
StrictDoc shall find inner doc comments and parse markers from it in those syntax positions,
and only in those positions, where the Rust language allows inner doc comments.
>>>
COMMENT: >>>
Inner doc comments are syntactic sugar for doc attributes.
Thus, the `allowed positions rule for attributes`_ applies.

.. _allowed positions rule for attributes: https://doc.rust-lang.org/reference/attributes.html#r-attributes.allowed-position
<<<

[REQUIREMENT]
UID: RUST-INNER-DOC-POS-FN
TITLE: Inner doc comments for functions
STATEMENT: >>>
StrictDoc shall find inner doc comments in function blocks.
<<<
RELATIONS:
- TYPE: Parent
  VALUE: RUST-INNER-DOC-POS

[REQUIREMENT]
UID: RUST-INNER-DOC-POS-MOD
TITLE: Inner doc comments for modules
STATEMENT: >>>
StrictDoc shall find inner doc comments in module blocks.
<<<

[REQUIREMENT]
UID: RUST-INNER-DOC-POS-EXT
TITLE: Inner doc comments for external blocks
STATEMENT: >>>
StrictDoc shall find inner doc comments in external blocks.
<<<

[REQUIREMENT]
UID: RUST-INNER-DOC-POS-IMPL
TITLE: Inner doc comments for implementation blocks
STATEMENT: >>>
StrictDoc shall find inner doc comments in implementation blocks.
<<<

[REQUIREMENT]
UID: RUST-OUTER-DOC-POS
TITLE: Allowed position for outer docs
STATEMENT: >>>
Consider `allowed position`_ s for outer doc comments:

- All item_ declarations
- Most statements
- Block expressions, but only when they are the outer expression of an
  expression statement or the final expression of another block expression.
- Enum variants, struct and union fields
- Generic lifetime or type parameter
- Expressions in limited situations
- Function, closure and function pointer parameters

.. _allowed position: https://doc.rust-lang.org/reference/attributes.html#r-attributes.allowed-position
.. _item: https://doc.rust-lang.org/reference/items.html#r-items.syntax
<<<
